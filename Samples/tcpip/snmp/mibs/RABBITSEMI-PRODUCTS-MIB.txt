-- *****************************************************************
-- RABBITSEMI-PRODUCTS-MIB.txt:  Rabbit Semiconductor Products MIB
--
-- April 2002  Stephen J. Hardy
--
-- Copyright (c) 2002 by Rabbit Semiconductor
-- All rights reserved.
-- 
-- *****************************************************************


RABBITSEMI-PRODUCTS-MIB DEFINITIONS ::= BEGIN

IMPORTS
	MODULE-IDENTITY
		FROM SNMPv2-SMI
	rabbitsemiModules,
	rabbitsemiProducts
		FROM RABBITSEMI-SMI;

rabbitsemiProductsMIB MODULE-IDENTITY
	LAST-UPDATED "200204020000Z"
	ORGANIZATION "Rabbit Semiconductor"
	CONTACT-INFO
		"	Rabbit Semiconductor
			Software Engineering

		Postal: 2900 Spafford Street
			Davis, CA  95616-6800
			USA

		   Tel: +1 530 757 4616

		E-mail: shardy@zworld.com"
	DESCRIPTION
		"This module defines the object identifiers that are
		assigned to various hardware platforms, and hence are
		returned as values for sysObjectID"
 	REVISION	"200204020000Z"
  	DESCRIPTION
		"Initial version of this MIB module."
	::= { rabbitsemiModules 2 }


-- Rabbit Semiconductor products employ the board ID as the
-- top level product object identifier.
bl1810	OBJECT IDENTIFIER ::= { rabbitsemiProducts 256 } -- 14MHz Jackrabbit
bl1800	OBJECT IDENTIFIER ::= { rabbitsemiProducts 257 } -- 29MHz Jackrabbit
bl1820	OBJECT IDENTIFIER ::= { rabbitsemiProducts 258 } -- 14MHz Jackrabbit, 32k SRAM
rcm2020	OBJECT IDENTIFIER ::= { rabbitsemiProducts 512 } -- 18MHz Core Module
rcm2010	OBJECT IDENTIFIER ::= { rabbitsemiProducts 513 } -- 25MHz Core Module, 128k SRAM
rcm2000	OBJECT IDENTIFIER ::= { rabbitsemiProducts 514 } -- 25MHz Core Module, 512k SRAM
op6600	OBJECT IDENTIFIER ::= { rabbitsemiProducts 768 } -- 18MHz Serial Display, no Ethernet
rtdk		OBJECT IDENTIFIER ::= { rabbitsemiProducts 769 } -- 18MHz TCP/IP Toolkit
op6700	OBJECT IDENTIFIER ::= { rabbitsemiProducts 770 } -- 18MHz Serial Display + Ethernet
sr9110   OBJECT IDENTIFIER ::= { rabbitsemiProducts 1281 } -- 18MHz Smart Star
sr9100   OBJECT IDENTIFIER ::= { rabbitsemiProducts 1282 } -- 25Mhz Smart Star
eg2000	OBJECT IDENTIFIER ::= { rabbitsemiProducts 1536 } -- 22MHz Ether Gate, two ethernet ports
rablink	OBJECT IDENTIFIER ::= { rabbitsemiProducts 1537 } -- 22MHz RabbitLink/EG2100
eg2020	OBJECT IDENTIFIER ::= { rabbitsemiProducts 1538 } -- 22MHz Ether Gate, one ethernet port
rcm2100  OBJECT IDENTIFIER ::= { rabbitsemiProducts 1792 } -- 22MHz Ethernet Core Module, ethernet, 512K Flash, 512K SRAM
rcm2110  OBJECT IDENTIFIER ::= { rabbitsemiProducts 1793 } -- 22MHz Ethernet Core Module, ethernet, 256K Flash, 128K SRAM
rcm2120  OBJECT IDENTIFIER ::= { rabbitsemiProducts 1794 } -- 22MHz Advanced Core Module, 512K Flash, 512K SRAM
rcm2130  OBJECT IDENTIFIER ::= { rabbitsemiProducts 1795 } -- 22MHz Advanced Core Module, 256K Flash, 128K SRAM
rcm2115  OBJECT IDENTIFIER ::= { rabbitsemiProducts 1796 } -- 22MHz Ethernet Core Module, ethernet, 256K Flash, 128K SRAM
bl2000	OBJECT IDENTIFIER ::= { rabbitsemiProducts 2048 } -- 22MHz 12 bit A/D, DAC,    Digital I/O, Ethernet
bl2010	OBJECT IDENTIFIER ::= { rabbitsemiProducts 2049 } -- 22MHz 10 bit A/D, no DAC, Digital I/O, Ethernet
bl2020	OBJECT IDENTIFIER ::= { rabbitsemiProducts 2050 } -- 22MHz 12 bit A/D, DAC,    Digital I/O, no Ethernet
bl2030	OBJECT IDENTIFIER ::= { rabbitsemiProducts 2051 } -- 22MHz 10 bit A/D, no DAC, Digital I/O, no Ethernet
bl2040   OBJECT IDENTIFIER ::= { rabbitsemiProducts 2052 } -- 22MHz Digital I/O, no analog, no Ethernet
rcm2200	OBJECT IDENTIFIER ::= { rabbitsemiProducts 2304 } -- 22MHz Micro Ethernet Core
rcm2300	OBJECT IDENTIFIER ::= { rabbitsemiProducts 2560 } -- 22MHz Micro Core
bl2100	OBJECT IDENTIFIER ::= { rabbitsemiProducts 2816 } -- 22MHz Mini-E, RCM2200 ethernet, analog I/O
bl2110	OBJECT IDENTIFIER ::= { rabbitsemiProducts 2817 } -- 22MHz Mini-E, RCM2200 ethernet, no analog I/O
bl2120	OBJECT IDENTIFIER ::= { rabbitsemiProducts 2818 } -- 22MHz Mini-E, RCM2300 no ethernet, analog I/O
bl2130	OBJECT IDENTIFIER ::= { rabbitsemiProducts 2819 } -- 22MHz Mini-E, RCM2300 no ethernet, no analog I/O
bl2105	OBJECT IDENTIFIER ::= { rabbitsemiProducts 2820 } -- 22MHz Mini-E, RCM2250 ethernet, analog I/O
bl2115	OBJECT IDENTIFIER ::= { rabbitsemiProducts 2821 } -- 22MHz Mini-E, RCM2250 ethernet, no analog I/O
sr9150 	OBJECT IDENTIFIER ::= { rabbitsemiProducts 3072 } -- 22MHz SmartStar CPU, ethernet
sr9160 	OBJECT IDENTIFIER ::= { rabbitsemiProducts 3073 } -- 22MHz SmartStar CPU, no ethernet
op6800	OBJECT IDENTIFIER ::= { rabbitsemiProducts 3328 } -- 22MHz MiniCom, RCM2200 ethernet
op6810	OBJECT IDENTIFIER ::= { rabbitsemiProducts 3329 } -- 22MHz MiniCom, RCM2300 no ethernet
op6805	OBJECT IDENTIFIER ::= { rabbitsemiProducts 3330 } -- 22MHz MiniCom, RCM2250 ethernet
rcm2250	OBJECT IDENTIFIER ::= { rabbitsemiProducts 3584 } -- 22MHz Micro Ethernet Core, 512KB RAM, 2x256KB flash
rcm3000	OBJECT IDENTIFIER ::= { rabbitsemiProducts 3840 } -- 29MHz RCM3000 Ethernet Core
rcm3010	OBJECT IDENTIFIER ::= { rabbitsemiProducts 3841 } -- 29MHz RCM3010 Ethernet Core

END
