-- *****************************************************************
-- RABBITSEMI-SMI.txt:  Rabbit Semiconductor Enterprise
--                      Structure of Management Information
--
-- April 2002  Stephen J. Hardy
--
-- Copyright (c) 2002 by Rabbit Semiconductor
-- All rights reserved.
-- 
-- *****************************************************************

RABBITSEMI-SMI DEFINITIONS ::= BEGIN

IMPORTS
	MODULE-IDENTITY,
	OBJECT-IDENTITY,
	enterprises
		FROM SNMPv2-SMI;

rabbitsemi MODULE-IDENTITY
	LAST-UPDATED "200204020000Z"
	ORGANIZATION "Rabbit Semiconductor"
	CONTACT-INFO
		"	Rabbit Semiconductor
			Software Engineering

		Postal: 2900 Spafford Street
			Davis, CA  95616-6800
			USA

		   Tel: +1 530 757 4616

		E-mail: shardy@zworld.com"
	DESCRIPTION
		"The Structure of Management Information for the
		Rabbit Semiconductor enterprise."
	REVISION      "200204020000Z"
	DESCRIPTION
		"Initial version of this MIB module."
	::= { enterprises 12807 }	-- assigned by IANA


rabbitsemiProducts OBJECT-IDENTITY
	STATUS	current
	DESCRIPTION
		"rabbitsemiProducts is the root OBJECT IDENTIFIER from
		which sysObjectID values are assigned.  Actual
		values are defined in RABBITSEMI-PRODUCTS-MIB."
	::= { rabbitsemi 1 }

rabbitsemiMgmt OBJECT-IDENTITY
	STATUS	current
	DESCRIPTION
		"rabbitsemiMgmt is the main subtree for new mib development."
	::= { rabbitsemi 2 }

oemExperiments OBJECT-IDENTITY
	STATUS	current
	DESCRIPTION
		"oemExperiments provides a root object identifier
		from which experimental mibs produced by other companies may be
		placed unilaterally.  This is also used for demonstrations
		and examples provided by Rabbit Semiconductor."
	::= { rabbitsemi 3 }

demos OBJECT-IDENTITY
	STATUS	current
	DESCRIPTION
		"oemExperiments.demos provides a root object identifier
		for demonstrations and examples provided by Rabbit Semiconductor."
	::= { oemExperiments 1 }

oemAssigned OBJECT-IDENTITY
	STATUS	current
	DESCRIPTION
		"oemAssigned provides a root object identifier
		from which mibs produced by other companies using Rabbit
		Semiconductor products may be placed, by registration with
		Rabbit Semiconductor."
	::= { rabbitsemi 4 }

rabbitsemiModules OBJECT-IDENTITY
	STATUS	current
	DESCRIPTION
		"rabbitsemiModules provides a root object identifier
		from which MODULE-IDENTITY values may be assigned."
	::= { rabbitsemi 5 }

rabbitsemiAgentCapability OBJECT-IDENTITY
	STATUS	current
	DESCRIPTION
		"rabbitsemiAgentCapability provides a root object identifier
		from which AGENT-CAPABILITIES values may be assigned."
	::= { rabbitsemi 6 }

rabbitsemiConfig OBJECT-IDENTITY
	STATUS	current
	DESCRIPTION
		"rabbitsemiConfig is the main subtree for configuration mibs."
	::= { rabbitsemi 7 }

rabbitsemiExperiments OBJECT-IDENTITY
	STATUS	current
	DESCRIPTION
		"rabbitsemiExperiments provides a root object identifier
		from which experimental mibs may be temporarily based."
	::= { rabbitsemi 8 }

rabbitsemiChipsets OBJECT-IDENTITY
	STATUS	current
	DESCRIPTION
		"rabbitsemiChipsets is the subtree for hardware chipset
		 information including processor and communication."
	::= { rabbitsemi 9 }

processor OBJECT-IDENTITY
	STATUS	current
	DESCRIPTION
		"rabbitsemiChipsets.processor."
	::= { rabbitsemiChipsets 1 }

communication OBJECT-IDENTITY
	STATUS	current
	DESCRIPTION
		"rabbitsemiChipsets.communication."
	::= { rabbitsemiChipsets 2 }

END
